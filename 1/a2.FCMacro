import math

App.setActiveDocument("__Ring")
App.ActiveDocument=App.getDocument("__Ring")
Gui.ActiveDocument=Gui.getDocument("__Ring")
# parameters ------------------------------
r1=76
ring_radius = -891.3
height=200
width=500
width_inner = width - 2*r1 #d = width -2*r1
# -----------------------------------------

f = open(r'C:\Users\attila\Desktop\ring\volumes.txt','w')


def calc_ring_volume():
	print 'Settings constraints'
	App.ActiveDocument.Sketch.setDatum(15,height)
	App.ActiveDocument.Sketch.setDatum(14,width_inner)
	App.ActiveDocument.Sketch.setDatum(3,r1)
	App.ActiveDocument.Sketch.setDatum(4,r1)
	App.ActiveDocument.Sketch.setDatum(13,-abs(ring_radius))
	#supress error on 2 hinges
	App.ActiveDocument.Sketch.setDatum(9,1e-2)
	App.ActiveDocument.Sketch.setDatum(10,1e-2)	
	App.ActiveDocument.recompute()	
	volume = App.ActiveDocument.getObject("Revolution").Shape.Volume
#	print "VOLUME: %.2f mm3"%(volume/10**6)
#	print (526.96 / volume/10**6)
	return volume

#width 2mm to max. 12mm in steps from 0.5mm
#For each width there will be about 20 different heights
for width in range(200,1200+1,50):
	for height in range(200,350+1,20):
		for ring_circum in range(4500,7600+1, 50):
			ring_radius = ring_circum / (2.0 * math.pi)
			width_inner = width - 2*r1
			vol = calc_ring_volume()	
			f.write('%s,%s,%s,%s\n'%(width,height,ring_circum,vol)) 
			f.flush()
